// Identifiants Unicode (accents) : le lexer accepte tout caractère alphabétique.
package Véhicule {
    part def Véhicule {
        attribute masseÉlevée : Integer;
        part moteurPrincipal : Véhicule;
    }
}
