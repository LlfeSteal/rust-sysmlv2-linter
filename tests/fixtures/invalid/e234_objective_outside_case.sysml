// Attendu : E234 (objective-outside-case) — `objective` n'est valide que
// dans un cas (`case def`, `analysis def`, `verification def`, `use case def`).
package P {
    requirement def R {
        objective o;
    }
}
