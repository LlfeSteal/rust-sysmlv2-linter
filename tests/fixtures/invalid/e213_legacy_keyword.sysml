// Attendu : E213 (legacy-keyword) — mots-clés SysML v1 / UML absents de SysML v2
package P {
    block Robot;
    value Masse;
    class Sensor;
    association Link;
    stereotype Marker;
    property x;
    operation compute;
}
