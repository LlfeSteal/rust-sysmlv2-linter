// Cas nominal : noms non restreints entre apostrophes, alias.
package QuotedNamesAndAlias {
    part def Robot;
    part 'mon robot préféré' : Robot;
    alias RobotFavori for 'mon robot préféré';
}
